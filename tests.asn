AttributeCertificateDefinitions {iso(1) member-body(2) by(112) 0 2 0 34 101
                                 67 module(1) ver1(1)} 

DEFINITIONS IMPLICIT TAGS ::=
BEGIN

id-pkix  OBJECT IDENTIFIER  ::=
         { iso(1) identified-organization(3) dod(6) internet(1)
                    security(5) mechanisms(5) pkix(7) }

-- PKIX arcs

id-pe OBJECT IDENTIFIER  ::=  { id-pkix 1 }
        -- arc for private certificate extensions
id-qt OBJECT IDENTIFIER ::= { id-pkix 2 }
        -- arc for policy qualifier types
id-kp OBJECT IDENTIFIER ::= { id-pkix 3 }
        -- arc for extended key purpose OIDS
id-ad OBJECT IDENTIFIER ::= { id-pkix 48 }
        -- arc for access descriptors

-- policyQualifierIds for Internet policy qualifiers

id-qt-cps      OBJECT IDENTIFIER ::=  { id-qt 1 }
      -- OID for CPS qualifier
id-qt-unotice  OBJECT IDENTIFIER ::=  { id-qt 2 }
      -- OID for user notice qualifier

-- access descriptor definitions

id-ad-ocsp         OBJECT IDENTIFIER ::= { id-ad 1 }
id-ad-caIssuers    OBJECT IDENTIFIER ::= { id-ad 2 }
id-ad-timeStamping OBJECT IDENTIFIER ::= { id-ad 3 }
id-ad-caRepository OBJECT IDENTIFIER ::= { id-ad 5 }

-- attribute data types

Attribute       ::=     SEQUENCE {
      type              AttributeType,
      values    SET OF AttributeValue }
            -- at least one value is required

AttributeType           ::=  OBJECT IDENTIFIER

AttributeValue          ::=  ANY

AttributeTypeAndValue           ::=     SEQUENCE {
        type    AttributeType,
        value   AttributeValue }

-- suggested naming attributes: Definition of the following
--   information object set may be augmented to meet local
--   requirements.  Note that deleting members of the set may
--   prevent interoperability with conforming implementations.
-- presented in pairs: the AttributeType followed by the
--   type definition for the corresponding AttributeValue
--Arc for standard naming attributes
id-at OBJECT IDENTIFIER ::= { joint-iso-ccitt(2) ds(5) 4 }

-- Naming attributes of type X520name

id-at-name              AttributeType ::= { id-at 41 }
id-at-surname           AttributeType ::= { id-at 4 }
id-at-givenName         AttributeType ::= { id-at 42 }
id-at-initials          AttributeType ::= { id-at 43 }
id-at-generationQualifier AttributeType ::= { id-at 44 }

X520name ::= CHOICE {
      teletexString     TeletexString   (SIZE (1..ub-name)),
      printableString   PrintableString (SIZE (1..ub-name)),
      universalString   UniversalString (SIZE (1..ub-name)),
      utf8String        UTF8String      (SIZE (1..ub-name)),
      bmpString         BMPString       (SIZE (1..ub-name)) }

-- Naming attributes of type X520CommonName

id-at-commonName        AttributeType ::= { id-at 3 }

X520CommonName ::= CHOICE {
      teletexString     TeletexString   (SIZE (1..ub-common-name)),
      printableString   PrintableString (SIZE (1..ub-common-name)),
      universalString   UniversalString (SIZE (1..ub-common-name)),
      utf8String        UTF8String      (SIZE (1..ub-common-name)),
      bmpString         BMPString       (SIZE (1..ub-common-name)) }

-- Naming attributes of type X520LocalityName

id-at-localityName      AttributeType ::= { id-at 7 }

X520LocalityName ::= CHOICE {
      teletexString     TeletexString   (SIZE (1..ub-locality-name)),
      printableString   PrintableString (SIZE (1..ub-locality-name)),
      universalString   UniversalString (SIZE (1..ub-locality-name)),
      utf8String        UTF8String      (SIZE (1..ub-locality-name)),
      bmpString         BMPString       (SIZE (1..ub-locality-name)) }

-- Naming attributes of type X520StateOrProvinceName

id-at-stateOrProvinceName AttributeType ::= { id-at 8 }

X520StateOrProvinceName ::= CHOICE {
      teletexString     TeletexString   (SIZE (1..ub-state-name)),
      printableString   PrintableString (SIZE (1..ub-state-name)),
      universalString   UniversalString (SIZE (1..ub-state-name)),
      utf8String        UTF8String      (SIZE (1..ub-state-name)),
      bmpString         BMPString       (SIZE(1..ub-state-name)) }

-- Naming attributes of type X520OrganizationName

id-at-organizationName  AttributeType ::= { id-at 10 }

X520OrganizationName ::= CHOICE {
      teletexString     TeletexString
                          (SIZE (1..ub-organization-name)),
      printableString   PrintableString
                          (SIZE (1..ub-organization-name)),
      universalString   UniversalString
                          (SIZE (1..ub-organization-name)),
      utf8String        UTF8String
                          (SIZE (1..ub-organization-name)),
      bmpString         BMPString
                          (SIZE (1..ub-organization-name))  }

-- Naming attributes of type X520OrganizationalUnitName

id-at-organizationalUnitName AttributeType ::= { id-at 11 }

X520OrganizationalUnitName ::= CHOICE {
      teletexString     TeletexString
                          (SIZE (1..ub-organizational-unit-name)),
      printableString   PrintableString
                          (SIZE (1..ub-organizational-unit-name)),
      universalString   UniversalString
                          (SIZE (1..ub-organizational-unit-name)),
      utf8String        UTF8String
                          (SIZE (1..ub-organizational-unit-name)),
      bmpString         BMPString
                          (SIZE (1..ub-organizational-unit-name)) }

-- Naming attributes of type X520Title

id-at-title             AttributeType ::= { id-at 12 }

X520Title ::= CHOICE {
      teletexString     TeletexString   (SIZE (1..ub-title)),
      printableString   PrintableString (SIZE (1..ub-title)),
      universalString   UniversalString (SIZE (1..ub-title)),
      utf8String        UTF8String      (SIZE (1..ub-title)),
      bmpString         BMPString       (SIZE (1..ub-title)) }

-- Naming attributes of type X520dnQualifier

id-at-dnQualifier       AttributeType ::= { id-at 46 }

X520dnQualifier ::=     PrintableString

-- Naming attributes of type X520countryName (digraph from IS 3166)

id-at-countryName       AttributeType ::= { id-at 6 }

X520countryName ::=     PrintableString (SIZE (2))

-- Naming attributes of type X520SerialNumber

id-at-serialNumber      AttributeType ::= { id-at 5 }

X520SerialNumber ::=    PrintableString (SIZE (1..ub-serial-number))

-- Naming attributes of type X520Pseudonym

id-at-pseudonym         AttributeType ::= { id-at 65 }

X520Pseudonym ::= CHOICE {
   teletexString     TeletexString   (SIZE (1..ub-pseudonym)),
   printableString   PrintableString (SIZE (1..ub-pseudonym)),
   universalString   UniversalString (SIZE (1..ub-pseudonym)),
   utf8String        UTF8String      (SIZE (1..ub-pseudonym)),
   bmpString         BMPString       (SIZE (1..ub-pseudonym)) }

-- Naming attributes of type DomainComponent (from RFC 2247)

id-domainComponent      AttributeType ::=
                          { 0 9 2342 19200300 100 1 25 }

DomainComponent ::=     IA5String

-- Legacy attributes

pkcs-9 OBJECT IDENTIFIER ::=
       { iso(1) member-body(2) us(840) rsadsi(113549) pkcs(1) 9 }

id-emailAddress          AttributeType ::= { pkcs-9 1 }

EmailAddress ::=         IA5String (SIZE (1..ub-emailaddress-length))

-- naming data types --

Name ::= CHOICE { -- only one possibility for now --
      rdnSequence  RDNSequence }

RDNSequence ::= SEQUENCE OF RelativeDistinguishedName

DistinguishedName ::=   RDNSequence

RelativeDistinguishedName  ::=
                    SET SIZE (1 .. MAX) OF AttributeTypeAndValue

-- Directory string type --

DirectoryString ::= CHOICE {
      teletexString             TeletexString   (SIZE (1..MAX)),
      printableString           PrintableString (SIZE (1..MAX)),
      universalString           UniversalString (SIZE (1..MAX)),
      utf8String              UTF8String      (SIZE (1..MAX)),
      bmpString               BMPString       (SIZE (1..MAX)) }

-- certificate and CRL specific structures begin here

Certificate  ::=  SEQUENCE  {
     tbsCertificate       TBSCertificate,
     signatureAlgorithm   AlgorithmIdentifier,
     signature            BIT STRING  }

TBSCertificate  ::=  SEQUENCE  {
     version         [0]  Version DEFAULT v1,
     serialNumber         CertificateSerialNumber,
     signature            AlgorithmIdentifier,
     issuer               Name,
     validity             Validity,
     subject              Name,
     subjectPublicKeyInfo SubjectPublicKeyInfo,
     issuerUniqueID  [1]  IMPLICIT UniqueIdentifier OPTIONAL,
                          -- If present, version MUST be v2 or v3
     subjectUniqueID [2]  IMPLICIT UniqueIdentifier OPTIONAL,
                          -- If present, version MUST be v2 or v3
     extensions      [3]  Extensions OPTIONAL
                          -- If present, version MUST be v3 --  }

Version  ::=  INTEGER  {  v1(0), v2(1), v3(2)  }

CertificateSerialNumber  ::=  INTEGER

Validity ::= SEQUENCE {
     notBefore      Time,
     notAfter       Time  }

Time ::= CHOICE {
     utcTime        UTCTime,
     generalTime    GeneralizedTime }

UniqueIdentifier  ::=  BIT STRING

SubjectPublicKeyInfo  ::=  SEQUENCE  {
     algorithm            AlgorithmIdentifier,
     subjectPublicKey     BIT STRING  }

Extensions  ::=  SEQUENCE SIZE (1..MAX) OF Extension

Extension  ::=  SEQUENCE  {
     extnID      OBJECT IDENTIFIER,
     critical    BOOLEAN DEFAULT FALSE,
     extnValue   OCTET STRING  }

-- CRL structures

CertificateList  ::=  SEQUENCE  {
     tbsCertList          TBSCertList,
     signatureAlgorithm   AlgorithmIdentifier,
     signature            BIT STRING  }

TBSCertList  ::=  SEQUENCE  {
     version                 Version OPTIONAL,
                                  -- if present, MUST be v2
     signature               AlgorithmIdentifier,
     issuer                  Name,
     thisUpdate              Time,
     nextUpdate              Time OPTIONAL,
     revokedCertificates     SEQUENCE OF SEQUENCE  {
          userCertificate         CertificateSerialNumber,
          revocationDate          Time,
          crlEntryExtensions      Extensions OPTIONAL
                                         -- if present, MUST be v2
                               }  OPTIONAL,
     crlExtensions           [0] Extensions OPTIONAL }
                                         -- if present, MUST be v2

-- Version, Time, CertificateSerialNumber, and Extensions were
-- defined earlier for use in the certificate structure

AlgorithmIdentifier  ::=  SEQUENCE  {
     algorithm               OBJECT IDENTIFIER,
     parameters              ANY DEFINED BY algorithm OPTIONAL  }
                                -- contains a value of the type
                                -- registered for use with the
                                -- algorithm object identifier value

-- X.400 address syntax starts here

ORAddress ::= SEQUENCE {
   built-in-standard-attributes BuiltInStandardAttributes,
   built-in-domain-defined-attributes
                   BuiltInDomainDefinedAttributes OPTIONAL,
   -- see also teletex-domain-defined-attributes
   extension-attributes ExtensionAttributes OPTIONAL }

-- Built-in Standard Attributes

BuiltInStandardAttributes ::= SEQUENCE {
   country-name                  CountryName OPTIONAL,
   administration-domain-name    AdministrationDomainName OPTIONAL,
   network-address           [0] IMPLICIT NetworkAddress OPTIONAL,
     -- see also extended-network-address
   terminal-identifier       [1] IMPLICIT TerminalIdentifier OPTIONAL,
   private-domain-name       [2] PrivateDomainName OPTIONAL,
   organization-name         [3] IMPLICIT OrganizationName OPTIONAL,
     -- see also teletex-organization-name
   numeric-user-identifier   [4] IMPLICIT NumericUserIdentifier
                                 OPTIONAL,
   personal-name             [5] IMPLICIT PersonalName OPTIONAL,
     -- see also teletex-personal-name
   organizational-unit-names [6] IMPLICIT OrganizationalUnitNames
                                 OPTIONAL }
     -- see also teletex-organizational-unit-names

CountryName ::= [APPLICATION 1] CHOICE {
   x121-dcc-code         NumericString
                           (SIZE (ub-country-name-numeric-length)),
   iso-3166-alpha2-code  PrintableString
                           (SIZE (ub-country-name-alpha-length)) }

AdministrationDomainName ::= [APPLICATION 2] CHOICE {
   numeric   NumericString   (SIZE (0..ub-domain-name-length)),
   printable PrintableString (SIZE (0..ub-domain-name-length)) }

NetworkAddress ::= X121Address  -- see also extended-network-address

X121Address ::= NumericString (SIZE (1..ub-x121-address-length))

TerminalIdentifier ::= PrintableString (SIZE
(1..ub-terminal-id-length))

PrivateDomainName ::= CHOICE {
   numeric   NumericString   (SIZE (1..ub-domain-name-length)),
   printable PrintableString (SIZE (1..ub-domain-name-length)) }

OrganizationName ::= PrintableString
                            (SIZE (1..ub-organization-name-length))
  -- see also teletex-organization-name

NumericUserIdentifier ::= NumericString
                            (SIZE (1..ub-numeric-user-id-length))

PersonalName ::= SET {
   surname     [0] IMPLICIT PrintableString
                    (SIZE (1..ub-surname-length)),
   given-name  [1] IMPLICIT PrintableString
                    (SIZE (1..ub-given-name-length)) OPTIONAL,
   initials    [2] IMPLICIT PrintableString
                    (SIZE (1..ub-initials-length)) OPTIONAL,
   generation-qualifier [3] IMPLICIT PrintableString
                    (SIZE (1..ub-generation-qualifier-length))
                    OPTIONAL }
  -- see also teletex-personal-name

OrganizationalUnitNames ::= SEQUENCE SIZE (1..ub-organizational-units)
                             OF OrganizationalUnitName
  -- see also teletex-organizational-unit-names

OrganizationalUnitName ::= PrintableString (SIZE
                    (1..ub-organizational-unit-name-length))

-- Built-in Domain-defined Attributes

BuiltInDomainDefinedAttributes ::= SEQUENCE SIZE
                    (1..ub-domain-defined-attributes) OF
                    BuiltInDomainDefinedAttribute

BuiltInDomainDefinedAttribute ::= SEQUENCE {
   type PrintableString (SIZE
                   (1..ub-domain-defined-attribute-type-length)),
   value PrintableString (SIZE
                   (1..ub-domain-defined-attribute-value-length)) }

-- Extension Attributes

ExtensionAttributes ::= SET SIZE (1..ub-extension-attributes) OF
               ExtensionAttribute

ExtensionAttribute ::=  SEQUENCE {
   extension-attribute-type [0] IMPLICIT INTEGER
                   (0..ub-extension-attributes),
   extension-attribute-value [1]
                   ANY DEFINED BY extension-attribute-type }

-- Extension types and attribute values

common-name INTEGER ::= 1

CommonName ::= PrintableString (SIZE (1..ub-common-name-length))

teletex-common-name INTEGER ::= 2

TeletexCommonName ::= TeletexString (SIZE (1..ub-common-name-length))

teletex-organization-name INTEGER ::= 3

TeletexOrganizationName ::=
                TeletexString (SIZE (1..ub-organization-name-length))

teletex-personal-name INTEGER ::= 4

TeletexPersonalName ::= SET {
   surname     [0] IMPLICIT TeletexString
                    (SIZE (1..ub-surname-length)),
   given-name  [1] IMPLICIT TeletexString
                    (SIZE (1..ub-given-name-length)) OPTIONAL,
   initials    [2] IMPLICIT TeletexString
                    (SIZE (1..ub-initials-length)) OPTIONAL,
   generation-qualifier [3] IMPLICIT TeletexString
                    (SIZE (1..ub-generation-qualifier-length))
                    OPTIONAL }

teletex-organizational-unit-names INTEGER ::= 5

TeletexOrganizationalUnitNames ::= SEQUENCE SIZE
      (1..ub-organizational-units) OF TeletexOrganizationalUnitName

TeletexOrganizationalUnitName ::= TeletexString
                  (SIZE (1..ub-organizational-unit-name-length))

pds-name INTEGER ::= 7

PDSName ::= PrintableString (SIZE (1..ub-pds-name-length))

physical-delivery-country-name INTEGER ::= 8

PhysicalDeliveryCountryName ::= CHOICE {
   x121-dcc-code NumericString (SIZE
(ub-country-name-numeric-length)),
   iso-3166-alpha2-code PrintableString
                  (SIZE (ub-country-name-alpha-length)) }

postal-code INTEGER ::= 9

PostalCode ::= CHOICE {
   numeric-code NumericString (SIZE (1..ub-postal-code-length)),
   printable-code PrintableString (SIZE (1..ub-postal-code-length)) }

physical-delivery-office-name INTEGER ::= 10

PhysicalDeliveryOfficeName ::= PDSParameter

physical-delivery-office-number INTEGER ::= 11

PhysicalDeliveryOfficeNumber ::= PDSParameter

extension-OR-address-components INTEGER ::= 12

ExtensionORAddressComponents ::= PDSParameter

physical-delivery-personal-name INTEGER ::= 13

PhysicalDeliveryPersonalName ::= PDSParameter

physical-delivery-organization-name INTEGER ::= 14

PhysicalDeliveryOrganizationName ::= PDSParameter

extension-physical-delivery-address-components INTEGER ::= 15

ExtensionPhysicalDeliveryAddressComponents ::= PDSParameter

unformatted-postal-address INTEGER ::= 16

UnformattedPostalAddress ::= SET {
   printable-address SEQUENCE SIZE (1..ub-pds-physical-address-lines)
         OF PrintableString (SIZE (1..ub-pds-parameter-length))
         OPTIONAL,
   teletex-string TeletexString
         (SIZE (1..ub-unformatted-address-length)) OPTIONAL }

street-address INTEGER ::= 17

StreetAddress ::= PDSParameter

post-office-box-address INTEGER ::= 18

PostOfficeBoxAddress ::= PDSParameter

poste-restante-address INTEGER ::= 19

PosteRestanteAddress ::= PDSParameter

unique-postal-name INTEGER ::= 20

UniquePostalName ::= PDSParameter

local-postal-attributes INTEGER ::= 21

LocalPostalAttributes ::= PDSParameter

PDSParameter ::= SET {
   printable-string PrintableString
                (SIZE(1..ub-pds-parameter-length)) OPTIONAL,
   teletex-string TeletexString
                (SIZE(1..ub-pds-parameter-length)) OPTIONAL }

extended-network-address INTEGER ::= 22

ExtendedNetworkAddress ::= CHOICE {
   e163-4-address SEQUENCE {
      number      [0] IMPLICIT NumericString
                       (SIZE (1..ub-e163-4-number-length)),
      sub-address [1] IMPLICIT NumericString
                       (SIZE (1..ub-e163-4-sub-address-length))
                       OPTIONAL },
   psap-address [0] IMPLICIT PresentationAddress }

PresentationAddress ::= SEQUENCE {
    pSelector     [0] EXPLICIT OCTET STRING OPTIONAL,
    sSelector     [1] EXPLICIT OCTET STRING OPTIONAL,
    tSelector     [2] EXPLICIT OCTET STRING OPTIONAL,
    nAddresses    [3] EXPLICIT SET SIZE (1..MAX) OF OCTET STRING }

terminal-type  INTEGER ::= 23

TerminalType ::= INTEGER {
   telex (3),
   teletex (4),
   g3-facsimile (5),
   g4-facsimile (6),
   ia5-terminal (7),
   videotex (8) } (0..ub-integer-options)

-- Extension Domain-defined Attributes

teletex-domain-defined-attributes INTEGER ::= 6

TeletexDomainDefinedAttributes ::= SEQUENCE SIZE
   (1..ub-domain-defined-attributes) OF TeletexDomainDefinedAttribute

TeletexDomainDefinedAttribute ::= SEQUENCE {
        type TeletexString
               (SIZE (1..ub-domain-defined-attribute-type-length)),
        value TeletexString
               (SIZE (1..ub-domain-defined-attribute-value-length)) }

--  specifications of Upper Bounds MUST be regarded as mandatory
--  from Annex B of ITU-T X.411 Reference Definition of MTS Parameter
--  Upper Bounds

-- Upper Bounds
ub-name INTEGER ::= 32768
ub-common-name INTEGER ::= 64
ub-locality-name INTEGER ::= 128
ub-state-name INTEGER ::= 128
ub-organization-name INTEGER ::= 64
ub-organizational-unit-name INTEGER ::= 64
ub-title INTEGER ::= 64
ub-serial-number INTEGER ::= 64
ub-match INTEGER ::= 128
ub-emailaddress-length INTEGER ::= 255
ub-common-name-length INTEGER ::= 64
ub-country-name-alpha-length INTEGER ::= 2
ub-country-name-numeric-length INTEGER ::= 3
ub-domain-defined-attributes INTEGER ::= 4
ub-domain-defined-attribute-type-length INTEGER ::= 8
ub-domain-defined-attribute-value-length INTEGER ::= 128
ub-domain-name-length INTEGER ::= 16
ub-extension-attributes INTEGER ::= 256
ub-e163-4-number-length INTEGER ::= 15
ub-e163-4-sub-address-length INTEGER ::= 40
ub-generation-qualifier-length INTEGER ::= 3
ub-given-name-length INTEGER ::= 16
ub-initials-length INTEGER ::= 5
ub-integer-options INTEGER ::= 256
ub-numeric-user-id-length INTEGER ::= 32
ub-organization-name-length INTEGER ::= 64
ub-organizational-unit-name-length INTEGER ::= 32
ub-organizational-units INTEGER ::= 4
ub-pds-name-length INTEGER ::= 16
ub-pds-parameter-length INTEGER ::= 30
ub-pds-physical-address-lines INTEGER ::= 6
ub-postal-code-length INTEGER ::= 16
ub-pseudonym INTEGER ::= 128
ub-surname-length INTEGER ::= 40
ub-terminal-id-length INTEGER ::= 24
ub-unformatted-address-length INTEGER ::= 180
ub-x121-address-length INTEGER ::= 16

-- Note - upper bounds on string types, such as TeletexString, are
-- measured in characters.  Excepting PrintableString or IA5String, a
-- significantly greater number of octets will be required to hold
-- such a value.  As a minimum, 16 octets, or twice the specified
-- upper bound, whichever is the larger, should be allowed for
-- TeletexString.  For UTF8String or UniversalString at least four
-- times the upper bound should be allowed.

id-ce OBJECT IDENTIFIER  ::=  {joint-iso-ccitt(2) ds(5) 29}

-- authority key identifier OID and syntax

id-ce-authorityKeyIdentifier OBJECT IDENTIFIER ::=  { id-ce 35 }

AuthorityKeyIdentifier ::= SEQUENCE {
    keyIdentifier             [0] KeyIdentifier            OPTIONAL,
    authorityCertIssuer       [1] GeneralNames             OPTIONAL,
    authorityCertSerialNumber [2] CertificateSerialNumber  OPTIONAL }
    -- authorityCertIssuer and authorityCertSerialNumber MUST both
    -- be present or both be absent

KeyIdentifier ::= OCTET STRING

-- subject key identifier OID and syntax

id-ce-subjectKeyIdentifier OBJECT IDENTIFIER ::=  { id-ce 14 }

SubjectKeyIdentifier ::= KeyIdentifier

-- key usage extension OID and syntax

id-ce-keyUsage OBJECT IDENTIFIER ::=  { id-ce 15 }

KeyUsage ::= BIT STRING {
     digitalSignature        (0),
     nonRepudiation          (1),
     keyEncipherment         (2),
     dataEncipherment        (3),
     keyAgreement            (4),
     keyCertSign             (5),
     cRLSign                 (6),
     encipherOnly            (7),
     decipherOnly            (8) }

-- private key usage period extension OID and syntax

id-ce-privateKeyUsagePeriod OBJECT IDENTIFIER ::=  { id-ce 16 }

PrivateKeyUsagePeriod ::= SEQUENCE {
     notBefore       [0]     GeneralizedTime OPTIONAL,
     notAfter        [1]     GeneralizedTime OPTIONAL }
     -- either notBefore or notAfter MUST be present

-- certificate policies extension OID and syntax

id-ce-certificatePolicies OBJECT IDENTIFIER ::=  { id-ce 32 }

anyPolicy OBJECT IDENTIFIER ::= { id-ce-certificatePolicies 0 }

CertificatePolicies ::= SEQUENCE SIZE (1..MAX) OF PolicyInformation

PolicyInformation ::= SEQUENCE {
     policyIdentifier   CertPolicyId,
     policyQualifiers   SEQUENCE SIZE (1..MAX) OF
             PolicyQualifierInfo OPTIONAL }

CertPolicyId ::= OBJECT IDENTIFIER

PolicyQualifierInfo ::= SEQUENCE {
       policyQualifierId  PolicyQualifierId,
       qualifier        ANY DEFINED BY policyQualifierId }

-- Implementations that recognize additional policy qualifiers MUST
-- augment the following definition for PolicyQualifierId

PolicyQualifierId ::=
    OBJECT IDENTIFIER ( id-qt-cps | id-qt-unotice )

-- CPS pointer qualifier

CPSuri ::= IA5String

-- user notice qualifier

UserNotice ::= SEQUENCE {
     noticeRef        NoticeReference OPTIONAL,
     explicitText     DisplayText OPTIONAL}

NoticeReference ::= SEQUENCE {
     organization     DisplayText,
     noticeNumbers    SEQUENCE OF INTEGER }

DisplayText ::= CHOICE {
     ia5String        IA5String      (SIZE (1..200)),
     visibleString    VisibleString  (SIZE (1..200)),
     bmpString        BMPString      (SIZE (1..200)),
     utf8String       UTF8String     (SIZE (1..200)) }

-- policy mapping extension OID and syntax

id-ce-policyMappings OBJECT IDENTIFIER ::=  { id-ce 33 }

PolicyMappings ::= SEQUENCE SIZE (1..MAX) OF SEQUENCE {
     issuerDomainPolicy      CertPolicyId,
     subjectDomainPolicy     CertPolicyId }

-- subject alternative name extension OID and syntax

id-ce-subjectAltName OBJECT IDENTIFIER ::=  { id-ce 17 }

SubjectAltName ::= GeneralNames

GeneralNames ::= SEQUENCE SIZE (1..MAX) OF GeneralName

GeneralName ::= CHOICE {
     otherName                       [0]     AnotherName,
     rfc822Name                      [1]     IA5String,
     dNSName                         [2]     IA5String,
     x400Address                     [3]     ORAddress,
     directoryName                   [4]     Name,
     ediPartyName                    [5]     EDIPartyName,
     uniformResourceIdentifier       [6]     IA5String,
     iPAddress                       [7]     OCTET STRING,
     registeredID                    [8]     OBJECT IDENTIFIER }

-- AnotherName replaces OTHER-NAME ::= TYPE-IDENTIFIER, as
-- TYPE-IDENTIFIER is not supported in the '88 ASN.1 syntax

AnotherName ::= SEQUENCE {
     type-id    OBJECT IDENTIFIER,
     value      [0] EXPLICIT ANY DEFINED BY type-id }

EDIPartyName ::= SEQUENCE {
     nameAssigner            [0]     DirectoryString OPTIONAL,
     partyName               [1]     DirectoryString }

-- issuer alternative name extension OID and syntax

id-ce-issuerAltName OBJECT IDENTIFIER ::=  { id-ce 18 }

IssuerAltName ::= GeneralNames

id-ce-subjectDirectoryAttributes OBJECT IDENTIFIER ::=  { id-ce 9 }

SubjectDirectoryAttributes ::= SEQUENCE SIZE (1..MAX) OF Attribute

-- basic constraints extension OID and syntax

id-ce-basicConstraints OBJECT IDENTIFIER ::=  { id-ce 19 }

BasicConstraints ::= SEQUENCE {
     cA                      BOOLEAN DEFAULT FALSE,
     pathLenConstraint       INTEGER (0..MAX) OPTIONAL }

-- name constraints extension OID and syntax

id-ce-nameConstraints OBJECT IDENTIFIER ::=  { id-ce 30 }

NameConstraints ::= SEQUENCE {
     permittedSubtrees       [0]     GeneralSubtrees OPTIONAL,
     excludedSubtrees        [1]     GeneralSubtrees OPTIONAL }

GeneralSubtrees ::= SEQUENCE SIZE (1..MAX) OF GeneralSubtree

GeneralSubtree ::= SEQUENCE {
     base                    GeneralName,
     minimum         [0]     BaseDistance DEFAULT 0,
     maximum         [1]     BaseDistance OPTIONAL }

BaseDistance ::= INTEGER (0..MAX)

-- policy constraints extension OID and syntax

id-ce-policyConstraints OBJECT IDENTIFIER ::=  { id-ce 36 }

PolicyConstraints ::= SEQUENCE {
     requireExplicitPolicy           [0] SkipCerts OPTIONAL,
     inhibitPolicyMapping            [1] SkipCerts OPTIONAL }

SkipCerts ::= INTEGER (0..MAX)

-- CRL distribution points extension OID and syntax

id-ce-cRLDistributionPoints     OBJECT IDENTIFIER  ::=  {id-ce 31}

CRLDistributionPoints ::= SEQUENCE SIZE (1..MAX) OF DistributionPoint

DistributionPoint ::= SEQUENCE {
     distributionPoint       [0]     DistributionPointName OPTIONAL,
     reasons                 [1]     ReasonFlags OPTIONAL,
     cRLIssuer               [2]     GeneralNames OPTIONAL }

DistributionPointName ::= CHOICE {
     fullName                [0]     GeneralNames,
     nameRelativeToCRLIssuer [1]     RelativeDistinguishedName }

ReasonFlags ::= BIT STRING {
     unused                  (0),
     keyCompromise           (1),
     cACompromise            (2),
     affiliationChanged      (3),
     superseded              (4),
     cessationOfOperation    (5),
     certificateHold         (6),
     privilegeWithdrawn      (7),
     aACompromise            (8) }

-- extended key usage extension OID and syntax

id-ce-extKeyUsage OBJECT IDENTIFIER ::= {id-ce 37}

ExtKeyUsageSyntax ::= SEQUENCE SIZE (1..MAX) OF KeyPurposeId


KeyPurposeId ::= OBJECT IDENTIFIER

-- permit unspecified key uses

anyExtendedKeyUsage OBJECT IDENTIFIER ::= { id-ce-extKeyUsage 0 }

-- extended key purpose OIDs

id-kp-serverAuth             OBJECT IDENTIFIER ::= { id-kp 1 }
id-kp-clientAuth             OBJECT IDENTIFIER ::= { id-kp 2 }
id-kp-codeSigning            OBJECT IDENTIFIER ::= { id-kp 3 }
id-kp-emailProtection        OBJECT IDENTIFIER ::= { id-kp 4 }
id-kp-timeStamping           OBJECT IDENTIFIER ::= { id-kp 8 }
id-kp-OCSPSigning            OBJECT IDENTIFIER ::= { id-kp 9 }

-- inhibit any policy OID and syntax

id-ce-inhibitAnyPolicy OBJECT IDENTIFIER ::=  { id-ce 54 }

InhibitAnyPolicy ::= SkipCerts

-- freshest (delta)CRL extension OID and syntax

id-ce-freshestCRL OBJECT IDENTIFIER ::=  { id-ce 46 }

FreshestCRL ::= CRLDistributionPoints

-- authority info access

id-pe-authorityInfoAccess OBJECT IDENTIFIER ::= { id-pe 1 }

AuthorityInfoAccessSyntax  ::=
        SEQUENCE SIZE (1..MAX) OF AccessDescription

AccessDescription  ::=  SEQUENCE {
        accessMethod          OBJECT IDENTIFIER,
        accessLocation        GeneralName  }

-- subject info access

id-pe-subjectInfoAccess OBJECT IDENTIFIER ::= { id-pe 11 }

SubjectInfoAccessSyntax  ::=
        SEQUENCE SIZE (1..MAX) OF AccessDescription

-- CRL number extension OID and syntax

id-ce-cRLNumber OBJECT IDENTIFIER ::= { id-ce 20 }

CRLNumber ::= INTEGER (0..MAX)

-- issuing distribution point extension OID and syntax

id-ce-issuingDistributionPoint OBJECT IDENTIFIER ::= { id-ce 28 }

IssuingDistributionPoint ::= SEQUENCE {
     distributionPoint          [0] DistributionPointName OPTIONAL,
     onlyContainsUserCerts      [1] BOOLEAN DEFAULT FALSE,
     onlyContainsCACerts        [2] BOOLEAN DEFAULT FALSE,
     onlySomeReasons            [3] ReasonFlags OPTIONAL,
     indirectCRL                [4] BOOLEAN DEFAULT FALSE,
     onlyContainsAttributeCerts [5] BOOLEAN DEFAULT FALSE }

id-ce-deltaCRLIndicator OBJECT IDENTIFIER ::= { id-ce 27 }

BaseCRLNumber ::= CRLNumber

-- CRL reasons extension OID and syntax

id-ce-cRLReasons OBJECT IDENTIFIER ::= { id-ce 21 }

CRLReason ::= ENUMERATED {
     unspecified             (0),
     keyCompromise           (1),
     cACompromise            (2),
     affiliationChanged      (3),
     superseded              (4),
     cessationOfOperation    (5),
     certificateHold         (6),
     removeFromCRL           (8),
     privilegeWithdrawn      (9),
     aACompromise           (10) }

-- certificate issuer CRL entry extension OID and syntax

id-ce-certificateIssuer OBJECT IDENTIFIER ::= { id-ce 29 }

CertificateIssuer ::= GeneralNames

-- hold instruction extension OID and syntax

id-ce-holdInstructionCode OBJECT IDENTIFIER ::= { id-ce 23 }

HoldInstructionCode ::= OBJECT IDENTIFIER

-- ANSI x9 holdinstructions

-- ANSI x9 arc holdinstruction arc

holdInstruction OBJECT IDENTIFIER ::=
          {joint-iso-itu-t(2) member-body(2) us(840) x9cm(10040) 2}

-- ANSI X9 holdinstructions referenced by this standard

id-holdinstruction-none OBJECT IDENTIFIER  ::=
                {holdInstruction 1} -- deprecated

id-holdinstruction-callissuer OBJECT IDENTIFIER ::=
                {holdInstruction 2}

id-holdinstruction-reject OBJECT IDENTIFIER ::=
                {holdInstruction 3}

-- invalidity date CRL entry extension OID and syntax

id-ce-invalidityDate OBJECT IDENTIFIER ::= { id-ce 24 }

InvalidityDate ::=  GeneralizedTime

-- Атрибутный сертификат 
AttributeCertificate ::= SEQUENCE {
  attrCertInfo      AttributeCertificateInfo,
  signatureAlgorithm    AlgorithmIdentifier,
  signatureValue    BIT STRING }


AttributeCertificateInfo ::= SEQUENCE {
  version                 AttCertVersion, -- версия должна быть v2
 holder                  Holder,
  issuer                  AttCertIssuer,
  signature               AlgorithmIdentifier,
  serialNumber            CertificateSerialNumber,
  attrCertValidityPeriod  AttCertValidityPeriod,
  attributes              SEQUENCE OF Attribute,
  issuerUniqueID          UniqueIdentifier OPTIONAL,
  extensions              Extensions OPTIONAL }

AttCertVersion ::= INTEGER {v2(1)}

Holder ::= SEQUENCE {
  baseCertificateID  [0]  IssuerSerial OPTIONAL,
  -- серийный номер СОК держателя и имя эмитента этого СОК
  entityName         [1]  GeneralNames OPTIONAL,
  -- имя держателя или роль
  objectDigestInfo   [2]  ObjectDigestInfo OPTIONAL
  -- используется для прямой аутентификации держателя

  -- по меньшей мере один из компонентов baseCertificateID, entityName или 
  -- objectDigestInfo должен присутствовать -- } 

ObjectDigestInfo ::= SEQUENCE {
  digestedObjectType ENUMERATED {
    publicKey        (0), 
    publicKeyCert    (1), 
    otherObjectTypes (2)},
  otherObjectTypeID   OBJECT IDENTIFIER OPTIONAL,
  digestAlgorithm     AlgorithmIdentifier,
  objectDigest        BIT STRING }

AttCertIssuer ::= [0] SEQUENCE {
  issuerName              GeneralNames OPTIONAL,
  baseCertificateID  [0]  IssuerSerial OPTIONAL,
  objectDigestInfo   [1]  ObjectDigestInfo OPTIONAL
  -- по меньшей мере один из компонентов issuerName, baseCertificateUD или 
  -- objectDigestInfo должен присутствовать -- }

IssuerSerial ::= SEQUENCE {
  issuer     GeneralNames,
  serial     CertificateSerialNumber,
  issuerUID  UniqueIdentifier OPTIONAL
}

AttCertValidityPeriod ::= SEQUENCE {
  notBeforeTime  GeneralizedTime,
  notAfterTime   GeneralizedTime
}

AttributeCertificationPath ::= SEQUENCE {
  attributeCertificate  AttributeCertificate,
  acPath                SEQUENCE OF ACPathData OPTIONAL
}

ACPathData ::= SEQUENCE {
  certificate           [0]  Certificate OPTIONAL,
  attributeCertificate  [1]  AttributeCertificate OPTIONAL
}

PrivilegePolicy ::= OBJECT IDENTIFIER

-- классы и их производные
OBJECT-CLASS ::= CLASS {
  &Superclasses           OBJECT-CLASS  OPTIONAL,
  &kind                   ObjectClassKind  DEFAULT  structural,
  &MandatoryAttributes    ATTRIBUTE  OPTIONAL,
  &OptionalAttributes     ATTRIBUTE  OPTIONAL,
  &id                     OBJECT IDENTIFIER  UNIQUE }
WITH SYNTAX {
  [SUBCLASS OF      &Superclasses]
  [KIND        &kind]
  [MUST CONTAIN      &MandatoryAttributes]
  [MAY CONTAIN      &OptionalAttributes]
  ID        &id }
ObjectClassKind ::= ENUMERATED {
  abstract    (0),
  structural    (1),
  auxiliary    (2) }

top OBJECT-CLASS ::= {
  KIND        abstract
  MUST CONTAIN      {objectClass}
  ID        id-oc-top }

objectClass ATTRIBUTE ::= {
  WITH SYNTAX      OBJECT IDENTIFIER
  EQUALITY MATCHING RULE  objectIdentifierMatch
  ID        id-at-objectClass }

ATTRIBUTE ::= CLASS {
  &derivation      ATTRIBUTE  OPTIONAL,
  &Type        OPTIONAL, 
  -- или &Type, или &derivation должны быть определены
  &equality-match    MATCHING-RULE  OPTIONAL,
  &ordering-match    MATCHING-RULE  OPTIONAL,
  &substrings-match    MATCHING-RULE  OPTIONAL,
  &single-valued    BOOLEAN  DEFAULT FALSE,
  &collective      BOOLEAN  DEFAULT FALSE,
  &dummy      BOOLEAN  DEFAULT FALSE,
  -- операции
  &no-user-modification  BOOLEAN  DEFAULT FALSE,
  &usage      AttributeUsage  DEFAULT userApplications,
  &id        OBJECT IDENTIFIER  UNIQUE }
WITH SYNTAX {
  [SUBTYPE OF      &derivation]
  [WITH SYNTAX      &Type]
  [EQUALITY MATCHING RULE  &equality-match]
  [ORDENING MATCHING RULE  &ordering-match]
  [SUBSTRINGS MATCHING RULE  &substrings-match]
  [SINGLE VALUE      &single-valued]
  [COLLECTIVE      &collective]
  [DUMMY      &dummy]
  [NO USER MODIFICATION  &no-user-modification]
  [USAGE      &usage]
  ID        &id }

AttributeUsage ::= ENUMERATED {
  userApplications  (0),
  directoryOperation  (1),
  distributedOperation  (2),
  dSAOperation    (3) }

MATCHING-RULE ::= CLASS {
  &ParentMatchingRules    OPTIONAL,
  &AssertionType    OPTIONAL,
  &uniqueMatchIndicator  ATTRIBUTE  OPTIONAL,
  &id        OBJECT IDENTIFIER  UNIQUE }
WITH SYNTAX {
  [PARENT      &ParentMatchingRules]
  [SYNTAX      &AssertionType]
  [UNIQUE-MATCH-INDICATOR  &uniqueMatchIndicator]
  ID        &id }
objectIdentifierMatch MATCHING-RULE ::= {
  SYNTAX      OBJECT IDENTIFIER
  ID        id-mr-objectIdentifierMatch }

EXTENSION ::= CLASS {
  &id        OBJECT IDENTIFIER  UNIQUE,
  &ExtnType }
WITH SYNTAX {
  SYNTAX      &ExtnType
  IDENTIFIED BY      &id }

-- атрибуты 
role ATTRIBUTE ::= {
  WITH SYNTAX       RoleSyntax
  ID                 id-at-role }

RoleSyntax ::= SEQUENCE {
  roleAuthority    [0]    GeneralNames OPTIONAL,
  roleName         [1]    GeneralName }

xmlPrivilegeInfo ATTRIBUTE ::= {
WITH SYNTAX        UTF8String  
     --содержит информацию о привилегии,
     -- закодированную в формате XML -  -
  ID                 id-at-xMLPrivilegeInfo }

permission ATTRIBUTE ::= {
  WITH SYNTAX               DualStringSyntax
  EQUALITY MATCHING RULE    dualStringMatch
  ID                        id-at-permission }

DualStringSyntax ::= SEQUENCE {
  operation      [0]    UnboundedDirectoryString,
  object         [1]    UnboundedDirectoryString }

UnboundedDirectoryString ::= CHOICE {
  teletexString     TeletexString   (SIZE(1..MAX)),
  printableString     PrintableString (SIZE (1..MAX)),
  bmpString       BMPString       (SIZE (1..MAX)),
  universalString     UniversalString (SIZE (1..MAX)),
  uTF8String       UTF8String      (SIZE (1..MAX)) }

dualStringMatch MATCHING-RULE ::= {
  SYNTAX        DualStringSyntax
  ID            id-mr-dualStringMatch }

timeSpecification EXTENSION ::= {
  SYNTAX             TimeSpecification
  IDENTIFIED BY      id-ce-timeSpecification }

TimeSpecification ::= SEQUENCE {
  time       CHOICE {
  absolute     SEQUENCE {
  startTime   [0]   GeneralizedTime OPTIONAL,
  endTime   [1]   GeneralizedTime OPTIONAL },
      periodic     SET SIZE (1..MAX) OF Period },
  notThisTime     BOOLEAN DEFAULT FALSE,
  timeZone     TimeZone OPTIONAL }
Period ::= SEQUENCE {
  timesOfDay     [0] SET SIZE (1..MAX) OF DayTimeBand OPTIONAL,
  days       [1] CHOICE {
      intDay     SET OF INTEGER,
      bitDay     BIT STRING { sunday (0), monday (1), tuesday (2), 
         wednesday (3), thursday (4), friday (5),
         saturday (6) },
      dayOf     XDayOf } OPTIONAL,
  weeks     [2] CHOICE {
      allWeeks     NULL,
      intWeek     SET OF INTEGER,
      bitWeek     BIT STRING { week1 (0), week2 (1), week3 (2), 
         week4 (3), week5 (4) } } OPTIONAL,
  months     [3] CHOICE {
      allMonths   NULL,
      intMonth     SET OF INTEGER,
      bitMonth     BIT STRING { january (0), february (1), march (2), 
              april (3), may (4), june (5), july (6), 
         august (7), september (8), october (9), 
         november (10), december (11) }
  } OPTIONAL,
  years     [4] SET OF INTEGER (1000 .. MAX) OPTIONAL }

XDayOf ::= CHOICE {
  first   [1]   NamedDay,
  second   [2]   NamedDay,
  third   [3]   NamedDay,
  fourth   [4]   NamedDay,
  fifth   [5]   NamedDay }

NamedDay ::= CHOICE {
  intNamedDays     ENUMERATED {
      sunday     (1),
      monday     (2),
      tuesday     (3),
      wednesday   (4),
      thursday     (5),
      friday     (6),
      saturday     (7) },
  bitNamedDays     BIT STRING { sunday (0), monday (1) , tuesday (2),
         wednesday (3), thursday (4), friday (5),
         saturday (6) }}

DayTimeBand ::= SEQUENCE {
  startDayTime     [0] DayTime DEFAULT { hour 0 },
  endDayTime     [1] DayTime DEFAULT { hour 23, minute 59, second 59 }}

DayTime ::= SEQUENCE {
  hour     [0]   INTEGER (0..23),
  minute   [1]   INTEGER (0..59) DEFAULT 0,
  second   [2]   INTEGER (0..59) DEFAULT 0 }

TimeZone ::= INTEGER (-12..12)

timeSpecificationMatch MATCHING-RULE ::= {
  SYNTAX      TimeSpecification
  ID          id-mr-timeSpecMatch }

targetingInformation EXTENSION ::= {
  SYNTAX           SEQUENCE SIZE (1..MAX) OF Targets
  IDENTIFIED BY    id-ce-targetInformation }

Targets ::= SEQUENCE SIZE (1..MAX) OF Target

Target ::= CHOICE {
  targetName     [0]    GeneralName,
  targetGroup    [1]    GeneralName,
  targetCert     [2]    TargetCert }

TargetCert ::= SEQUENCE {
  targetCertificate     IssuerSerial,
  targetName            GeneralName OPTIONAL,
  certDigestInfo        ObjectDigestInfo OPTIONAL }

userNotice EXTENSION ::= {
  SYNTAX           SEQUENCE SIZE (1..MAX) OF UserNotice
  IDENTIFIED BY    id-ce-userNotice }

acceptablePrivilegePolicies EXTENSION ::= {
  SYNTAX           AcceptablePrivilegePoliciesSyntax
  IDENTIFIED BY    id-ce-acceptablePrivilegePolicies }

AcceptablePrivilegePoliciesSyntax ::= SEQUENCE SIZE (1..MAX) OF PrivilegePolicy

singleUse EXTENSION ::= {
  SYNTAX           NULL
  IDENTIFIED BY    id-ce-singleUse }

groupAC EXTENSION ::= {
  SYNTAX           NULL
  IDENTIFIED BY    id-ce-groupAC }

noRevAvail EXTENSION ::= {
  SYNTAX           NULL
  IDENTIFIED BY    id-ce-noRevAvail }

sOAIdentifier EXTENSION ::= {
  SYNTAX           NULL
  IDENTIFIED BY    id-ce-sOAIdentifier }

sOAIdentifierMatch MATCHING-RULE ::= {
  SYNTAX      NULL
  ID          id-mr-sOAIdentifierMatch }

attributeDescriptor EXTENSION ::= {
  SYNTAX           AttributeDescriptorSyntax
  IDENTIFIED BY    id-ce-attributeDescriptor }

AttributeDescriptorSyntax ::= SEQUENCE {
  identifier         AttributeIdentifier,
  attributeSyntax    OCTET STRING(SIZE (1..MAX)),
  name             [0]  AttributeName OPTIONAL,
  description      [1]  AttributeDescription OPTIONAL,
  dominationRule        PrivilegePolicyIdentifier }

AttributeIdentifier ::= ATTRIBUTE.&id
AttributeName ::= UTF8String(SIZE (1..MAX))

AttributeDescription ::= UTF8String(SIZE (1..MAX))

PrivilegePolicyIdentifier ::= SEQUENCE {
  privilegePolicy    PrivilegePolicy,
  privPolSyntax      InfoSyntax }

InfoSyntax ::= CHOICE {
  content      UnboundedDirectoryString,
  pointer      SEQUENCE { 
      name      GeneralNames,
      hash      SEQUENCE {
      algorithmIdentifier  AlgorithmIdentifier,
      hashedPolicyInfo  BIT STRING 
      -- содержит хэш-значение от DER-кодированного содержимого, указанного 
      -- по адресу name -- } OPTIONAL } }

attDescriptor MATCHING-RULE ::= {
  SYNTAX      AttributeDescriptorSyntax
  ID          id-mr-attDescriptorMatch }

roleSpecCertIdentifier EXTENSION ::= {
  SYNTAX           RoleSpecCertIdentifierSyntax
  IDENTIFIED BY    id-ce-roleSpecCertIdentifier }

RoleSpecCertIdentifierSyntax ::= SEQUENCE SIZE (1..MAX) OF RoleSpecCertIdentifier

RoleSpecCertIdentifier ::= SEQUENCE {
  roleName              [0]  GeneralName,
  roleCertIssuer        [1]  GeneralName,
  roleCertSerialNumber  [2]  CertificateSerialNumber OPTIONAL,
  roleCertLocator       [3]  GeneralNames OPTIONAL }

roleSpecCertIdMatch MATCHING-RULE ::= {
  SYNTAX      RoleSpecCertIdentifierSyntax
  ID          id-mr-roleSpecCertIdMatch }

basicAttConstraints EXTENSION ::= {
  SYNTAX           BasicAttConstraintsSyntax
  IDENTIFIED BY    id-ce-basicAttConstraints }

BasicAttConstraintsSyntax ::= SEQUENCE {
  authority            BOOLEAN DEFAULT FALSE,
  pathLenConstraint    INTEGER(0..MAX) OPTIONAL }

basicAttConstraintsMatch MATCHING-RULE ::= {
  SYNTAX      BasicAttConstraintsSyntax
  ID          id-mr-basicAttConstraintsMatch }

delegatedNameConstraints EXTENSION ::= {
  SYNTAX           NameConstraintsSyntax
  IDENTIFIED BY    id-ce-delegatedNameConstraints }

delegatedNameConstraintsMatch MATCHING-RULE ::= {
  SYNTAX      NameConstraintsSyntax
  ID          id-mr-delegatedNameConstraintsMatch }
NameConstraintsSyntax ::= SEQUENCE {
  permittedSubtrees    [0]  GeneralSubtrees OPTIONAL,
  excludedSubtrees     [1]  GeneralSubtrees OPTIONAL
  -- как минимум один из компонентов должен присутствовать -- }

acceptableCertPolicies EXTENSION ::= {
  SYNTAX           AcceptableCertPoliciesSyntax
  IDENTIFIED BY    id-ce-acceptableCertPolicies }

AcceptableCertPoliciesSyntax ::= SEQUENCE SIZE (1..MAX) OF CertPolicyId

acceptableCertPoliciesMatch MATCHING-RULE ::= {
  SYNTAX      AcceptableCertPoliciesSyntax
  ID          id-mr-acceptableCertPoliciesMatch }

authorityAttributeIdentifier EXTENSION ::= {
  SYNTAX           AuthorityAttributeIdentifierSyntax
  IDENTIFIED BY    id-ce-authorityAttributeIdentifier }

AuthorityAttributeIdentifierSyntax ::= SEQUENCE SIZE (1..MAX) OF AuthAttId

AuthAttId ::= IssuerSerial

authAttIdMatch MATCHING-RULE ::= {
  SYNTAX      AuthorityAttributeIdentifierSyntax
  ID          id-mr-authAttIdMatch }

indirectIssuer EXTENSION ::= {
  SYNTAX           NULL
  IDENTIFIED BY    id-ce-indirectIssuer }

issuedOnBehalfOf EXTENSION ::= {
  SYNTAX           GeneralName
  IDENTIFIED BY    id-ce-issuedOnBehalfOf }

noAssertion EXTENSION ::= {
  SYNTAX           NULL
  IDENTIFIED BY    id-ce-noAssertion }

allowedAttributeAssignments EXTENSION ::= {
  SYNTAX           AllowedAttributeAssignments
  IDENTIFIED BY    id-ce-allowedAttAss }

AllowedAttributeAssignments ::= SET OF SEQUENCE {
  attributes    [0] SET OF CHOICE {
      attributeType       [0] AttributeType,
      attributeTypeandValues  [1] Attribute },
  holderDomain    [1] GeneralName }

attributeMappings EXTENSION ::= {
  SYNTAX           AttributeMappings
  IDENTIFIED BY    id-ce-attributeMappings }

AttributeMappings ::= SET OF CHOICE {
  typeMappings          [0] SEQUENCE {
      local         [0]  AttributeType,
      remote        [1]  AttributeType},

  typeValueMappings  [1] SEQUENCE {
      local         [0]  AttributeTypeAndValue,
      remote        [1]  AttributeTypeAndValue }}

holderNameConstraints EXTENSION ::= {
  SYNTAX           HolderNameConstraintsSyntax
  IDENTIFIED BY    id-ce-holderNameConstraints }

HolderNameConstraintsSyntax ::= SEQUENCE {
  permittedSubtrees    [0]  GeneralSubtrees,
  excludedSubtrees     [1]  GeneralSubtrees OPTIONAL
}

-- типы ИУП 
pmiUser OBJECT-CLASS ::= {
  SUBCLASS OF      {top}
  KIND             auxiliary
  MAY CONTAIN      {attributeCertificateAttribute}
  ID               id-oc-pmiUser }

pmiAA OBJECT-CLASS ::= { -- ЦАС для ИУП
  SUBCLASS OF      {top}
  KIND             auxiliary
  MAY CONTAIN    {aACertificate | attributeCertificateRevocationList |
         attributeAuthorityRevocationList}
  ID               id-oc-pmiAA }

pmiSOA OBJECT-CLASS ::= { -- источник привилегий
  SUBCLASS OF      {top}
  KIND             auxiliary
  MAY CONTAIN    {attributeCertificateRevocationList |
                    attributeAuthorityRevocationList |
                    attributeDescriptorCertificate}
  ID               id-oc-pmiSOA }

attCertCRLDistributionPt OBJECT-CLASS ::= {
  SUBCLASS OF      {top}
  KIND             auxiliary
  MAY CONTAIN    {attributeCertificateRevocationList |
                    attributeAuthorityRevocationList}
  ID               id-oc-attCertCRLDistributionPts }

pmiDelegationPath OBJECT-CLASS ::= {
  SUBCLASS OF      {top}
  KIND             auxiliary
  MAY CONTAIN      {delegationPath}
  ID               id-oc-pmiDelegationPath }

privilegePolicy OBJECT-CLASS ::= {
  SUBCLASS OF      {top}
  KIND             auxiliary
  MAY CONTAIN      {privPolicy}
  ID               id-oc-privilegePolicy }

protectedPrivilegePolicy OBJECT-CLASS ::= {
  SUBCLASS OF     {top}
  KIND             auxiliary
  MAY CONTAIN      {protPrivPolicy}
  ID               id-oc-protectedPrivilegePolicy }
-- атрибуты справочника ИУП 
attributeCertificateAttribute ATTRIBUTE ::= {
  WITH SYNTAX             AttributeCertificate
  EQUALITY MATCHING RULE  attributeCertificateExactMatch
  ID                      id-at-attributeCertificate }

aACertificate ATTRIBUTE ::= {
  WITH SYNTAX             AttributeCertificate
  EQUALITY MATCHING RULE  attributeCertificateExactMatch
  ID                      id-at-aACertificate }

attributeDescriptorCertificate ATTRIBUTE ::= {
  WITH SYNTAX             AttributeCertificate
  EQUALITY MATCHING RULE  attributeCertificateExactMatch
  ID                      id-at-attributeDescriptorCertificate }

attributeCertificateRevocationList ATTRIBUTE ::= {
  WITH SYNTAX             CertificateList
  EQUALITY MATCHING RULE  certificateListExactMatch
  ID                      id-at-attributeCertificateRevocationList }

attributeAuthorityRevocationList ATTRIBUTE ::= {
  WITH SYNTAX             CertificateList
  EQUALITY MATCHING RULE  certificateListExactMatch
  ID                      id-at-attributeAuthorityRevocationList }

delegationPath ATTRIBUTE ::= {
  WITH SYNTAX      AttCertPath
  ID               id-at-delegationPath }

AttCertPath ::= SEQUENCE OF AttributeCertificate

privPolicy ATTRIBUTE ::= {
  WITH SYNTAX      PolicySyntax
  ID               id-at-privPolicy }

PolicySyntax ::= SEQUENCE {
  policyIdentifier    PolicyID,
  policySyntax        InfoSyntax }

PolicyID ::= CertPolicyId

protPrivPolicy ATTRIBUTE ::= {
  WITH SYNTAX             AttributeCertificate
  EQUALITY MATCHING RULE  attributeCertificateExactMatch
  ID                      id-at-protPrivPolicy
}

xmlPrivPolicy ATTRIBUTE ::= {
  WITH SYNTAX      UTF8String -- содержит информацию о политике
             -- применения привилегии в формате XML -    -
  ID               id-at-xmlPrivPolicy }

-- правила соответствия 

certificateListExactMatch MATCHING-RULE ::= {
  SYNTAX      CertificateListExactAssertion
  ID          id-mr-certificateListExactMatch }
CertificateListExactAssertion ::= SEQUENCE {
  issuer               Name,
  thisUpdate           Time,
  distributionPoint    DistributionPointName OPTIONAL }

attributeCertificateExactMatch MATCHING-RULE ::= {
  SYNTAX      AttributeCertificateExactAssertion
  ID          id-mr-attributeCertificateExactMatch }

AttributeCertificateExactAssertion ::= SEQUENCE {
  serialNumber    CertificateSerialNumber,
  issuer          AttCertIssuer }

attributeCertificateMatch MATCHING-RULE ::= {
  SYNTAX      AttributeCertificateAssertion
  ID          id-mr-attributeCertificateMatch }

AttributeCertificateAssertion ::= SEQUENCE {
  holder    [0]  CHOICE {
      baseCertificateID    [0]  IssuerSerial,
      holderName           [1]  GeneralNames} OPTIONAL,
  issuer             [1]  GeneralNames OPTIONAL,
  attCertValidity    [2]  GeneralizedTime OPTIONAL,
  attType            [3]  SET OF AttributeType OPTIONAL 
  -- как минимум один из компонентов holder, issuer, attCertValidity 
  -- или attType должен присутствовать --}

holderIssuerMatch MATCHING-RULE ::= {
  SYNTAX      HolderIssuerAssertion
  ID          id-mr-holderIssuerMatch }

HolderIssuerAssertion ::= SEQUENCE {
  holder      [0]  Holder OPTIONAL,
  issuer      [1]  AttCertIssuer OPTIONAL }

delegationPathMatch MATCHING-RULE ::= {
  SYNTAX      DelMatchSyntax
  ID          id-mr-delegationPathMatch }

DelMatchSyntax ::= SEQUENCE {
  firstIssuer      AttCertIssuer,
  lastHolder       Holder }

extensionPresenceMatch MATCHING-RULE ::= {
  SYNTAX      EXTENSION.&id
  ID          id-mr-extensionPresenceMatch }

-- идентификаторы 

id-mr          OBJECT IDENTIFIER ::= {joint-iso-itu-t(2) ds(5) 13}

id-oc          OBJECT IDENTIFIER ::= {joint-iso-itu-t(2) ds(5) 6}

-- классы объектов
id-oc-top              OBJECT IDENTIFIER ::= {id-oc 0}

id-oc-pmiUser               OBJECT IDENTIFIER ::= {id-oc 24}

id-oc-pmiAA               OBJECT IDENTIFIER ::= {id-oc 25}

id-oc-pmiSOA               OBJECT IDENTIFIER ::= {id-oc 26}

id-oc-attCertCRLDistributionPts        OBJECT IDENTIFIER ::= {id-oc 27}

id-oc-privilegePolicy             OBJECT IDENTIFIER ::= {id-oc 32}

id-oc-pmiDelegationPath          OBJECT IDENTIFIER ::= {id-oc 33}

id-oc-protectedPrivilegePolicy           OBJECT IDENTIFIER ::= {id-oc 34}

-- атрибуты 
id-at-objectClass            OBJECT IDENTIFIER ::= {id-at 0}

id-at-attributeCertificate          OBJECT IDENTIFIER ::= {id-at 58}

id-at-attributeCertificateRevocationList    OBJECT IDENTIFIER ::= {id-at 59}

id-at-aACertificate             OBJECT IDENTIFIER ::= {id-at 61}

id-at-attributeDescriptorCertificate         OBJECT IDENTIFIER ::= {id-at 62}

id-at-attributeAuthorityRevocationList      OBJECT IDENTIFIER ::= {id-at 63}

id-at-privPolicy             OBJECT IDENTIFIER ::= {id-at 71}

id-at-role              OBJECT IDENTIFIER ::= {id-at 72}

id-at-delegationPath             OBJECT IDENTIFIER ::= {id-at 73}

id-at-protPrivPolicy             OBJECT IDENTIFIER ::= {id-at 74}

id-at-xMLPrivilegeInfo           OBJECT IDENTIFIER ::= {id-at 75}

id-at-xmlPrivPolicy             OBJECT IDENTIFIER ::= {id-at 76}

id-at-permission             OBJECT IDENTIFIER ::= {id-at 82}

-- расширения атрибутных сертификатов 
id-ce-authorityAttributeIdentifier         OBJECT IDENTIFIER ::= {id-ce 38}

id-ce-roleSpecCertIdentifier           OBJECT IDENTIFIER ::= {id-ce 39}

id-ce-basicAttConstraints           OBJECT IDENTIFIER ::= {id-ce 41}

id-ce-delegatedNameConstraints         OBJECT IDENTIFIER ::= {id-ce 42}

id-ce-timeSpecification           OBJECT IDENTIFIER ::= {id-ce 43}

id-ce-attributeDescriptor           OBJECT IDENTIFIER ::= {id-ce 48}

id-ce-userNotice             OBJECT IDENTIFIER ::= {id-ce 49}

id-ce-sOAIdentifier             OBJECT IDENTIFIER ::= {id-ce 50}

id-ce-acceptableCertPolicies           OBJECT IDENTIFIER ::= {id-ce 52}

id-ce-targetInformation           OBJECT IDENTIFIER ::= {id-ce 55}

id-ce-noRevAvail             OBJECT IDENTIFIER ::= {id-ce 56}

id-ce-acceptablePrivilegePolicies         OBJECT IDENTIFIER ::= {id-ce 57}

id-ce-indirectIssuer             OBJECT IDENTIFIER ::= {id-ce 61}

id-ce-noAssertion             OBJECT IDENTIFIER ::= {id-ce 62}

id-ce-issuedOnBehalfOf           OBJECT IDENTIFIER ::= {id-ce 64}

id-ce-singleUse             OBJECT IDENTIFIER ::= {id-ce 65}

id-ce-groupAC               OBJECT IDENTIFIER ::= {id-ce 66}

id-ce-allowedAttAss             OBJECT IDENTIFIER ::= {id-ce 67}

id-ce-attributeMappings           OBJECT IDENTIFIER ::= {id-ce 68}

id-ce-holderNameConstraints           OBJECT IDENTIFIER ::= {id-ce 69}

-- правила соответствия
id-mr-objectIdentifierMatch          OBJECT IDENTIFIER ::= {id-mr 0}

id-mr-certificateListExactMatch         OBJECT IDENTIFIER ::= {id-mr 38}

id-mr-attributeCertificateMatch         OBJECT IDENTIFIER ::= {id-mr 42}

id-mr-attributeCertificateExactMatch         OBJECT IDENTIFIER ::= {id-mr 45}

id-mr-holderIssuerMatch           OBJECT IDENTIFIER ::= {id-mr 46}

id-mr-authAttIdMatch             OBJECT IDENTIFIER ::= {id-mr 53}

id-mr-roleSpecCertIdMatch           OBJECT IDENTIFIER ::= {id-mr 54}

id-mr-basicAttConstraintsMatch         OBJECT IDENTIFIER ::= {id-mr 55}

id-mr-delegatedNameConstraintsMatch         OBJECT IDENTIFIER ::= {id-mr 56}

id-mr-timeSpecMatch             OBJECT IDENTIFIER ::= {id-mr 57}

id-mr-attDescriptorMatch           OBJECT IDENTIFIER ::= {id-mr 58}

id-mr-acceptableCertPoliciesMatch         OBJECT IDENTIFIER ::= {id-mr 59}

id-mr-delegationPathMatch           OBJECT IDENTIFIER ::= {id-mr 61}

id-mr-sOAIdentifierMatch           OBJECT IDENTIFIER ::= {id-mr 66}

id-mr-extensionPresenceMatch           OBJECT IDENTIFIER ::= {id-mr 67}

id-mr-dualStringMatch             OBJECT IDENTIFIER ::= {id-mr 69}

END
